# untitled

## #1: Can sense Ain when PVARP idle (Informational)
DDD pacemaker requires A-V sychrony, when not in PVARP period, must be able to sense Ain.

## #2: Back to Idle after sensed Ain (Functional)
DDD pacemaker requires A-V sychrony, when not in PVARP period, must be able to sense Ain.

## #3: State Sensed Ain (Functional)
When Atrial signal be sent during PVARP_idle state, transite to this state.

## #4: PVARP subsystem (Functional)
DDD pacemaker requires not make Atrial and Ventricular events too close to each other. So after a V event, must wait a interval, during which cannot sense new Atrial signals.

## #5: State PVARP block (Functional)
In this state, All Atrial signal should be ignored.

## #6: State PVARP Idle (Functional)
Initial state of PVARP, must be able to sense Atrial signal and Ventricular signal and do transitions.

## #7: Back to idle when PVARP ends (Functional)
When PVARP period ends, must go back to idle state.

## #8: When VS or VP sensed, got blocked (Functional)
During Idle state, when VS or VP were sensed, PVARP got blocked, and ignore all A signals.

## #9: Timer discount (Functional)
Discount timer until TPVARP_cur <=0, then transfer to idle.

## #10: Ignore Ain when PVARP blocked (Functional)
In order not to make Atrial and Ventricular events too close to each other, Atrial signal must be ignored when PVARP blocked.

## #11: State PVARP ARgot (Functional)
In order not to make Atrial and Ventricular events too close to each other, Atrial signal must be ignored when PVARP blocked.

## #12: Back to block after sensed Ain (Functional)
After got an AR, go back to blocked state.

## #13: State VRP idle (Functional)
The inital state of VRP, when sensed VS or VP was generated, transfers to block state.

## #14: VRP subsystem (Functional)
A DDD pacemaker should never give VP during VRP, for which may cause ventricular fibrillation.

## #15: State VRP VSgot (Functional)
when sensed a VS signal, transfer from this state to block state.

## #16: Blocked when VP was sent (Functional)
After a VP was sent, start the timer of VRP subsystem, and got blocked.

## #17: Transfer to VSgot when Vin sensed (Functional)
After a Vin signal sensed, transfer to VSgot state.

## #18: State VRP block (Functional)
After a ventricular event, go to this state until VRP timer discount to 0.

## #19: Timer discount (Functional)
Discount timer until TVRP_cur <=0, then transfer to idle.

## #20: Transfer to idle when VRP ends (Functional)
When PVARP period ends, must go back to idle state.

## #21: LRI subsystem (Functional)
A DDD pacemaker should maintain the heart rate no slower than the minimum heart rate.

## #22: Back to idle after VP (Functional)
After a VP signal sensed, LRI should be reset (back to idle state)

## #23: State LRI VPgot (Functional)
During LRI block state, when a VP signal sensed, transfer to this state.

## #24: State LRI idle (Functional)
The initial state of LRI subsystem, should be able to be blocked when Atrial signal sensed.

## #25: Timer discount (Functional)
Discount timer until TLRI_cur <= TLRI_def, then transfer to blocked state.

## #26: Timer reset (Functional)
When VS or VP sensed, reset LRI timer.

## #27: Got blocked when Ain sensed (Functional)
During LRI idle state, when Ain was sensed, transfer to LRI block state.

## #28: Sent AP and got blocked (Functional)
When timer discount to TLRI_def, sends AP and got blocked.

## #29: Back to Idle when V signal sensed. (Functional)
When Vin was sensed or VP was sent, reset it to idle state.

## #30: State LRI block (Functional)
During this state, pacemaker should wait until Ventricular events occur.

## #31: Timer discount (Functional)
Discount timer until TLRI_cur <= 0, then transfer to VPgot state and send a VP to maintain lower heart rate.

## #32: Reset AP (Functional)
If Atrial Pace sent, reset it to false.

## #33: Give VP when LRI timer less than 0 (Functional)
A DDD pacemaker should give VP when LRI timer less than 0, to maintain heartrate >= 60bpm.

## #34: Init transfer LRI (Functional)
Initialize of LRI.

## #35: Init transfer VRP (Functional)
Initialize of VRP.

## #36: Init transfer PVARP (Functional)
Initialize of PVARP.

## #37: Init transfer AVI (Functional)
Initialize of AVI.

## #38: Init transfer URI (Functional)
Initialize of URI.

## #39: AVI subsystem (Functional)
A DDD pacemaker should consider A-V synchrony, which is, after an atrial event, if no ventricular events happen during AVI, then send VP.

## #40: State AVI idle (Functional)
Idle state of AVI, should be able to get blocked when Atrial events happen.

## #41: State AVI block (Functional)
when atrial event sensed, got blocked and start a timer. If no ventricular events happen during this interval, gives a VP.

## #42: State AVI VPgot (Functional)
Send VP when timer dicount to 0.

## #43: Got blocked at atrial event (Functional)
Got blocked at atrial event, and wait for ventricular events happen.

## #44: back to idle at ventricular event (Functional)
back to idle at ventricular event, and wait for an atrial event happen.

## #45: Timer discount (Functional)
Discount timer until TAVI_cur <= 0, then transfer to VPgot state and send a VP to maintain normal heart rate.

## #46: Reset VP (Functional)
After giving a VP, reset VP to false

## #47: Send VP if no ventricular events happen (Functional)
Send VP if no ventricular events happen, to maintain normal heart rate.

## #48: URI subsystem (Functional)
A DDD pacemaker should maintain the heart rate no faster than the maximum heart rate.

## #49: Reset VS (Functional)
After sensing a Vin signal, reset VS to false.

## #50: State URI idle (Functional)
The initial state of URI, when VS or VP sensed, should be able to got blocked.

## #51: State URI blocked (Functional)
Blocked URI when Ventriculer events happen, ensure not to send VP during this period.

## #52: Timer discount (Functional)
Discount timer until TURI_cur <= 0, then transfer to idle state.

## #53: Go back to idle when timer less than 0 (Functional)
When URI period ends, go back to Idle state.

## #54: Blocked when Ventricular signal sensed (Functional)
Pacemaker should get blocked when Ventricular signal sensed.

## #55: Reset timer at VS or VP (Functional)
When a ventricular event sensed(VS or VP), reset the timer.
